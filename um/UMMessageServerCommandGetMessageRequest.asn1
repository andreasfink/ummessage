UMMessageServerCommandGetMessageRequest::= SEQUENCE
{
    command         [0] INTEGER,
    flags           [1] INTEGER,
    sequenceNumber  [2] INTEGER,
    instance        [3] UTF8String,
    messageId       [4] UTF8String,
}
