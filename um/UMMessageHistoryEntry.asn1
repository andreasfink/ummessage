MessageHistoryEntry ::= SEQUENCE
{
    archiveId       [1] UTF8String,
    instance        [2] UTF8String,
    messageId       [3] UTF8String,
    msisdn          [4] UTF8String,
    ts              [5] UTF8String,
    delay           [6] REAL,
    text            [7] UTF8String,
}
