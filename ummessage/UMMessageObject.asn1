UMMessageObject ::= SEQUENCE
{
    archive-id                    [1] UTF8String,
    archive-status                [2] INTEGER,
    instance                      [3] UTF8String,
    message-id                    [4] UTF8String,
    username                      [5] UTF8String,
    groupname                     [6] UTF8String,
    delivery-method               [7] UTF8String,
    submission-type               [8] UTF8String,
    purge-flag                    [9] INTEGER,
    user-flags                    [10] INTEGER,
    retry-pattern-table           [11] UTF8String,
    type                          [12] UTF8String,
    network-error-code            [13] INTEGER,
    vas-esme                      [14] UTF8String,
    vas-ip                        [15] UTF8String,
    exported                      [16] INTEGER,
    options                       [17] UTF8String,
    from-number                   [20] UTF8String,
    from-msc                      [21] UTF8String,
    from-imsi                     [22] UTF8String,
    from-ip                       [23] UTF8String,
    from-country                  [24] UTF8String,
    from-operator-code            [25] UTF8String,
    from-operator-name            [26] UTF8String,
    to-number                     [30] UTF8String,
    to-msc                        [31] UTF8String,
    to-imsi                       [32] UTF8String,
    to-ip                         [33] UTF8String,
    to-country                    [34] UTF8String,
    to-operator-code              [35] UTF8String,
    to-operator-name              [36] UTF8String,
    delivery-report-address       [40] UTF8String,
    delivery-report-msc           [41] UTF8String,
    delivery-report-imsi          [42] UTF8String,
    delivery-report-ip            [43] UTF8String,
    delivery-report-mask          [50] INTEGER,
    alerting-address              [51] UTF8String,
    dlr-text                      [52] UTF8String,
    replace-if-present            [53] INTEGER,
    opc-srism                     [54] UTF8String,
    dpc-srism                     [55] UTF8String,
    opc-fsm                       [56] UTF8String,
    dpc-fsm                       [57] UTF8String,
    smsc-srism-gt                 [60] UTF8String,
    smsc-srism-map                [62] UTF8String,
    smsc-fsm-gt                   [61] UTF8String,
    smsc-fsm-map                  [63] UTF8String,
    hlr                           [64] UTF8String,
    tt-srism                      [65] INTEGER,
    tt-fsm                        [66] INTEGER,
    hlr-override                  [67] UTF8String,
    created                       [70] UTF8String,
    scts                          [71] UTF8String,
    scts-tz                       [72] UTF8String,
    qpriority                     [73] INTEGER,
    upriority                     [74] INTEGER,
    message-priority              [75] INTEGER,
    billing-type                  [76] INTEGER,
    test-flag                     [77] INTEGER,
    deferred                      [78] UTF8String,
    message-status                [80] UTF8String,
    message-error                 [81] INTEGER,
    message-delivered             [82] UTF8String,
    failed                        [83] UTF8String,
    attempted                     [84] UTF8String,
    validity                      [85] UTF8String,
    next-attempt                  [86] UTF8String,
    attempts                      [87] INTEGER,
    max-attempts                  [88] INTEGER,
    message-waiting-set           [89] INTEGER,
    delivery-report-status        [90] UTF8String,
    delivery-report-error         [91] INTEGER,
    delivery-report-delivered     [92] UTF8String,
    delivery-report-failed        [93] UTF8String,
    delivery-report-attempted     [94] UTF8String,
    delivery-report-expiry        [95] UTF8String,
    delivery-report-next-attempt  [96] UTF8String,
    delivery-report-attempts      [97] INTEGER,
    delivery-report-max-attempts  [98] INTEGER,
    delivery-report-waiting-set   [99] INTEGER,
    msu-count-sri-sm-tx           [100] INTEGER,
    msu-count-sri-sm-rx           [101] INTEGER,
    msu-count-sri-sm-htx          [102] INTEGER,
    msu-count-sri-sm-hrx          [103] INTEGER,
    msu-count-sri-sm-crx          [104] INTEGER,
    msu-count-fsm-tx              [105] INTEGER,
    msu-count-fsm-rx              [106] INTEGER,
    msu-count-tcap-handshake-tx   [107] INTEGER,
    msu-count-tcap-handshake-rx   [108] INTEGER,
    phone-ref                     [110] INTEGER,
    udhi                          [111] INTEGER,
    reply-path-indicator          [112] INTEGER,
    pid                           [113] INTEGER,
    compress                      [114] INTEGER,
    dcs                           [115] INTEGER,
    mwi                           [116] INTEGER,
    udh                           [117] OCTETSTRING,
    content                       [118] OCTETSTRING,
    plaintext-content             [119] UTF8String,
    message-class                 [120] INTEGER,
    coding                        [121] UTF8String,
    extension-data                [122] UTF8String,
    esm-class                     [123] INTEGER,
    cost-table                    [130] UTF8String,
    msu-cost-tx                   [131] REAL,
    msu-cost-rx                   [132] REAL,
    sms-cost                      [133] REAL,
    interworking-cost             [134] REAL,
    interworking-tap-code         [135] UTF8String,
    total-cost                    [136] REAL,
    charge-table1                 [137] UTF8String,
    charge-price1                 [138] REAL,
    currency1                     [139] UTF8String,
    profit1                       [140] REAL,
    charge-table2                 [141] UTF8String,
    charge-price2                 [142] REAL,
    currency2                     [143] UTF8String,
    profit2                       [144] REAL,
    destination-quota-table       [145] UTF8String,
    comment                       [150] UTF8String,
    user-message-reference        [151] OCTETSTRING,
    user-reference                [152] UTF8String,
    provider-reference            [153] UTF8String,
    router-reference              [154] UTF8String,
    multipart-ref                 [155] INTEGER,
    current-part                  [156] INTEGER,
    max-parts                     [157] INTEGER,
    linked-message-id             [158] UTF8String,
    inbound-message-ids           [159] UTF8String,
    outbound-message-ids          [160] UTF8String,
    submit-timestamp              [170] UTF8String,
    submit-ack-timestamp          [171] UTF8String,
    submit-err-timestamp          [172] UTF8String,
    submit-string                 [173] UTF8String,
    submit-error-code             [174] INTEGER,
    auto-routed                   [180] UTF8String,
    route-id                      [181] UTF8String,
    subroute-id                   [182] UTF8String,
    routed-on-prefix              [183] UTF8String
}
