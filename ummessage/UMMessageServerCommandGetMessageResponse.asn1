UMMessageServerCommandGetMessageResponse ::= SEQUENCE
{
    command         [0] INTEGER,
    flags           [1] INTEGER,
    sequenceNumber  [2] INTEGER,
    status          [3] INTEGER,
    error           [4] UTF8String OPTIONAL,
    message         [5] UMMessageObject OPTIONAL,
}
